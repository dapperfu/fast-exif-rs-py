[DOCUMENT]
TITLE: "Nikon HE/HE* RAW Viewing Support"
UID: NEF-HE-VIEW
VERSION: "1.0"
DATE: "2025-10-20"

[GRAMMAR]
ELEMENTS:
- TAG: GROUP
  PROPERTIES:
    IS_COMPOSITE: True
  FIELDS:
  - TITLE: TITLE
    TYPE: String
    REQUIRED: True
- TAG: REQUIREMENT
  PROPERTIES:
    PREFIX: REQ
  FIELDS:
  - TITLE: TITLE
    TYPE: String
    REQUIRED: True
  - TITLE: STATEMENT
    TYPE: String
    REQUIRED: True
  - TITLE: RATIONALE
    TYPE: String
    REQUIRED: False
  - TITLE: STATUS
    TYPE: SingleChoice(Draft, Active, Deleted)
    REQUIRED: True

[[GROUP]]
TITLE: "Scope and Objectives"

[REQUIREMENT]
TITLE: Goal definition
STATEMENT: The system SHALL enable viewing Nikon High Efficiency (HE/HE*) RAW still images in feh via imlib2 on Linux without using proprietary SDKs.
RATIONALE: Users require open-source viewing of Nikon HE/HE* stills.
STATUS: Draft

[REQUIREMENT]
TITLE: Immediate preview fallback
STATEMENT: The system SHALL provide an immediate preview fallback by extracting and displaying the embedded JPEG preview from HE/HE* NEF files.
RATIONALE: Guarantees near-term usability while full decoding is developed.
STATUS: Draft

[REQUIREMENT]
TITLE: True RAW decoding path
STATEMENT: The system SHOULD implement a clean-room reverse-engineered decoder for Nikon HE/HE* compressed RAW to reconstruct a 14-bit CFA image for visualization.
RATIONALE: Enables accurate RAW rendering beyond preview.
STATUS: Draft

[[/GROUP]]

[[GROUP]]
TITLE: "Constraints and Non-Functional"

[REQUIREMENT]
TITLE: Userspace only
STATEMENT: The implementation SHALL operate entirely in userspace without sudo and without modifying system Python.
RATIONALE: Complies with environment constraints.
STATUS: Draft

[REQUIREMENT]
TITLE: Virtual environment
STATEMENT: All Python tooling SHALL use a virtual environment named venv, and Makefile references SHALL use venv/bin/* paths.
RATIONALE: Avoids system pollution and ensures reproducibility.
STATUS: Draft

[REQUIREMENT]
TITLE: Typing and documentation
STATEMENT: All Python scripts SHALL have full mypy-compliant typing and numpy-style docstrings.
RATIONALE: Code quality and maintainability.
STATUS: Draft

[[/GROUP]]

[[GROUP]]
TITLE: "Interfaces and Deliverables"

[REQUIREMENT]
TITLE: Probing tool
STATEMENT: Provide tools/nef_probe.py to enumerate TIFF IFDs, key tags, and detect HE/HE*.
RATIONALE: Aids corpus analysis and debugging.
STATUS: Draft

[REQUIREMENT]
TITLE: Preview extraction tool
STATEMENT: Provide tools/nef_extract_preview.py to extract the embedded JPEG preview without external binaries.
RATIONALE: Enables immediate viewing in feh via a wrapper flow.
STATUS: Draft

[REQUIREMENT]
TITLE: imlib2 integration
STATEMENT: Provide an imlib2 loader or fallback logic to use HE/HE* decoder output, with preview fallback on failure.
RATIONALE: Integrates with feh display path.
STATUS: Draft

[[/GROUP]]

[[GROUP]]
TITLE: "Acceptance Criteria"

[REQUIREMENT]
TITLE: feh display success
STATEMENT: feh SHALL display HE/HE* NEF files either via decoded RAW or via embedded JPEG fallback with correct orientation.
RATIONALE: Verifies end-user goal.
STATUS: Draft

[REQUIREMENT]
TITLE: Tooling behavior
STATEMENT: nef_probe.py SHALL identify HE/HE* characteristics; nef_extract_preview.py SHALL reliably output a JPEG for input HE/HE* NEFs.
RATIONALE: Validates intermediate deliverables.
STATUS: Draft

[[/GROUP]]
